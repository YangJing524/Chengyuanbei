FME workspace 路况.fmw

Parameters:
- DestDataset_GEODATABASE_FILE = C:\Users\yj\Desktop\城 · 垣\路网畅通情况数据库\实时路网畅阻情况数据.gdb   # File Geodatabase
- SourceDataset_FILEGDB_3 = $(FME_MF_DIR)额济纳旗边界shp\路况.gdb   # 文件 Geodatabase
- SourceDataset_ESRISHAPE_3 = C:\Users\yj\Desktop\城 · 垣\基础数据库\北京市_西城区.shp   # Source Esri Shapefile(s)

Readers:
- FILEGDB_1: FILEGDB from $(SourceDataset_FILEGDB_3)
- ESRISHAPE_1: ESRISHAPE from $(SourceDataset_ESRISHAPE_3)

Writers:
- GEODATABASE_FILE_1: GEODATABASE_FILE to $(DestDataset_GEODATABASE_FILE)

市辖区 (reader ESRISHAPE_1)
    attributes: OBJECTID long, AREA double, PERIMETER double, BOUNT_ double, BOUNT_ID double, GBCODE char(6), ADCODE99 char(6), NAME99 char(40), SH2 char(2), DI2 char(2), X2 char(2), CENTROID_Y double, CENTROID_X double, Shape_Leng double, Shape_Area double
    -> 2DGridAccumulator
    -> SpatialFilter [Filter]
2DGridAccumulator
    COL_ATTR = _column
    GRID_TYPE = Polygons
    ROW_ATTR = _row
    SIZE_TYPE = Cell Size
    STARTINGCORNER = Lower Left
    XINC = 0.02
    YINC = 0.02
    GRID -> SpatialFilter [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> DateTimeStamper
DateTimeStamper
    DATETIME_ATTR = _timestamp
    INCLUDE_OFFSET = NO
    STAMP_TYPE = datetime
    TIMEZONE = local
    -> BoundsExtractor
BoundsExtractor
    XMAX = _xmax
    XMIN = _xmin
    YMAX = _ymax
    YMIN = _ymin
    -> AttributeRounder
AttributeRounder
    PLACES = 6
    ROUND_TYPE = Nearest
    SRC_ATTRS = _xmax _ymax _xmin _ymin
    -> 获取路况 [Decelerator_Input]
获取路况
    _XMAX = @Value(_xmax)
    _XMIN = @Value(_xmin)
    _YMAX = @Value(_ymax)
    _YMIN = @Value(_ymin)
    JSONFragmenter_Fragments -> AttributeSplitter
AttributeSplitter
    ATTR_NAME = polyline
    DELIMITER = ;
    DROP_EMPTY_PARTS = No
    LIST_NAME = _list
    TRIM_OPTION = Both
    -> ListExploder
ListExploder
    ATTR_ACCUM_MODE = Merge List Attributes
    ATTR_CONFLICT_RES = Use List Attribute Values
    INDEX_ATTR = _element_index
    LIST_ATTR = _list{}
    ELEMENTS -> AttributeSplitter_2
AttributeSplitter_2
    ATTR_NAME = _list
    DELIMITER = ,
    DROP_EMPTY_PARTS = No
    LIST_NAME = _xy
    TRIM_OPTION = Both
    -> VertexCreator
VertexCreator
    MODE_NAME = Replace with Point
    XVAL = @Value(_xy{0})
    YVAL = @Value(_xy{1})
    -> LineBuilder
LineBuilder
    ACCUM_INPUT_ATTRS = Use Attributes From One Feature
    BREAKATTR = json_index _column _row
    REMOVE_DUPLICATES = No
    LINE -> DuplicateFilter
DuplicateFilter
    INPUT_ORDERED_CHOICE = No
    KEYATTR = direction name status angle
    UNIQUE -> AttributeCreator
    UNIQUE -> DuplicateFilter_Unique
DuplicateFilter_Unique: Inspector
AttributeCreator
    ATTR_TABLE = SET_TO 路况 = FME_CONDITIONAL:DEFAULT_VALUE'_FME_NO_OP_'BOOL_OP;OR;COMPOSITE_TEST;<Unused>;TEST @Value(status) = 0'未知'BOOL_OP;OR;COMPOSITE_TEST;<Unused>;TEST @Value(status) = 1'畅通'BOOL_OP;OR;COMPOSITE_TEST;<Unused>;TEST @Value(status) = 2'缓行'BOOL_OP;OR;COMPOSITE_TEST;<Unused>;TEST @Value(status) = 3'拥堵'FME_NUM_CONDITIONS5___
    -> line (writer GEODATABASE_FILE_1)
    -> AttributeCreator_Output
AttributeCreator_Output: Inspector
line (writer GEODATABASE_FILE_1)
    attributes: 路况 char(200), _timestamp date, name char(200), status char(200), direction char(200), angle char(200), speed char(200)

FME custom transformer 获取路况

Parameters:
- _XMAX = @Value(_xmax)   # Xmax
- _YMAX = @Value(_ymax)   # Ymax
- _XMIN = @Value(_xmin)   # Xmin
- _YMIN = @Value(_ymin)   # Ymin

Decelerator_Input (input)
    -> AttributeCreator
Note: 计数器
AttributeCreator
    ATTR_TABLE = SET_TO n = 0
    -> HTTPCaller
Input (input)
    -> HTTPCaller
Note: 通过API与矩形框访问路况信息
HTTPCaller
    ADDITIONAL_URL_PARAMETERS = rectangle;@Value(_xmin),@Value(_ymin);@Value(_xmax),@Value(_ymax) key;b01803a8d6382fc3dbeaf2d7fcf319df city;西安
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://restapi.amap.com/v3/traffic/status/rectangle?
    TRANSFER_TIMEOUT_LENGTH = 90
    USE_COOKIES = No
    VERIFY_SSL_CERTIFICATES = Yes
    -> JSONFragmenter
    <REJECTED> -> Decelerator
JSONFragmenter
    EXPLODE_FORMAT = JSON
    EXTRACT_ATTR = Yes
    JSON_ATTR = _response_body
    JSON_QUERY = json["trafficinfo"]["roads"][*]
    NEW_ATTRIBUTES = name status direction angle speed polyline
    READ_FROM_FILE = NO
    RECURSIVE = Yes
    REJECT_EMPTY_LISTS = YES
    FRAGMENTS -> JSONFragmenter_Fragments (output)
    <REJECTED> -> Decelerator
JSONFragmenter_Fragments (output)
Decelerator
    DECEL_TYPE = Per Feature Delay
    DELAY = 1
    -> AttributeCreator_2
AttributeCreator_2
    ATTR_TABLE = SET_TO n = @Evaluate(@Value(n)+1)
    -> Tester
Tester
    BOOL_OP = OR
    COMPOSITE_TEST = 1
    TEST_CLAUSE = TEST @Value(n) < 3
    TEST_MODE = TEST
    PASSED -> Input (output)
Input (output)
