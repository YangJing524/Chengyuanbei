FME workspace 道路畅通状况.fmw

Parameters:
- SourceDataset_ESRISHAPE = C:\Users\yj\Desktop\城 · 垣\基础数据库\北京市_西城区.shp   # Source Esri Shapefile(s)
- FEATURE_TYPES =
- DestDataset_JSON = C:\Users\YJ\Desktop\西城区格网坐标点.json   # Destination JSON (JavaScript Object Notation) File
- DestDataset_FILEGDB = $(FME_MF_DIR)实时路网畅阻情况数据.gdb   # 文件 Geodatabase

Readers:
- ESRISHAPE_1: ESRISHAPE from $(SourceDataset_ESRISHAPE)

Writers:
- JSON_1: JSON to $(DestDataset_JSON)
- FILEGDB_1: FILEGDB to $(DestDataset_FILEGDB)

Note: 北京市_西城区
北京市_西城区 (reader ESRISHAPE_1)
    attributes: Id long
    -> BoundingBoxReplacer
    -> SpatialFilter [Filter]
BoundingBoxReplacer
    BOXTYPE = 2D Bounding Box
    BOX -> Reprojector
Note: WGS84
Reprojector
    DEST = LL-WGS84
    INTERPOLATION_TYPE_NAME = Nearest Neighbor
    RASTER_CELL_SIZE = Preserve Cells
    RASTER_TOLERANCE = 0.0
    SOURCE = Read from feature
    REPROJECTED -> 2DGridAccumulator
2DGridAccumulator
    COL_ATTR = _column
    GRID_TYPE = Polygons
    ROW_ATTR = _row
    SIZE_TYPE = Cell Size
    STARTINGCORNER = Lower Left
    XINC = 0.002
    YINC = 0.002
    GRID -> SpatialFilter [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> BoundsExtractor
BoundsExtractor
    XMAX = _xmax
    XMIN = _xmin
    YMAX = _ymax
    YMIN = _ymin
    -> AttributeRounder
AttributeRounder
    PLACES = 6
    ROUND_TYPE = Nearest
    SRC_ATTRS = _xmin _ymax _xmax _ymin
    -> PythonCaller
    -> 北京市_西城区 (writer FILEGDB_1)
北京市_西城区 (writer FILEGDB_1)
    attributes: _xmax text(200), _xmin text(200), _ymax text(200), _ymin text(200)
PythonCaller
    NEW_ATTRIBUTES = _jsonBounding
    PYTHONSOURCE:
      import fme
      import fmeobjects
      from collections import OrderedDict
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.d={}
              self.id=0
              self.feature=[]
          def input(self,feature):
              x_min=feature.getAttribute('_xmin')
              y_min=feature.getAttribute('_ymin')
              x_max=feature.getAttribute('_xmax')
              y_max=feature.getAttribute('_ymax')

              self.d[self.id]={'x_min':x_min,'y_min':y_min,'x_max':x_max,'y_max':y_max}

              self.id+=1
              self.feature.append(feature)

          def close(self):
              for feature in self.feature:
                  feature.setAttribute('_jsonBounding',str(self.d))
                  self.pyoutput(feature)
    PYTHONSYMBOL = FeatureProcessor
    -> Sampler_2
Sampler_2
    RATE = 1
    SAMPLE_MODE = No
    SAMPLE_TYPE_LONG = Last N Features
    SAMPLED -> 北京市_西城区 (writer JSON_1)
北京市_西城区 (writer JSON_1)
    attributes: _jsonBounding string
